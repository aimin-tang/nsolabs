module banner-rfs {

  namespace "http://example.com/banner-rfs";
  prefix banner-rfs;

  import ietf-inet-types {
    prefix inet;
  }
  import tailf-common {
    prefix tailf;
  }
  import tailf-ncs {
    prefix ncs;
  }

  description
    "Bla bla...";

  revision 2016-01-01 {
    description
      "Initial revision.";
  }

  list banner-rfs {
    description "This is an RFS skeleton service";
    key msg;

    leaf msg {
      tailf:info "Unique service id";
      type string;
    }

    uses ncs:service-data;
    ncs:servicepoint banner-rfs-servicepoint;

    leaf device {
      type leafref {
        path "/ncs:devices/ncs:device/ncs:name";
      }
    }
  }
}
