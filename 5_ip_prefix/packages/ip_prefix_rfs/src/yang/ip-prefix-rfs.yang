module ip-prefix-rfs {

  namespace "http://testlab.com/ip-prefix-rfs";
  prefix ip-prefix-rfs;

  import ietf-inet-types {
    prefix inet;
  }
  import tailf-common {
    prefix tailf;
  }
  import tailf-ncs {
    prefix ncs;
  }

  description
    "Bla bla...";

  revision 2016-01-01 {
    description
      "Initial revision.";
  }

  list ip-prefix-rfs {
    description "This is an RFS skeleton service";

    key list-name;
    leaf list-name {
      tailf:info "ip prefix list name";
      type string;
    }

    uses ncs:service-data;
    ncs:servicepoint ip-prefix-rfs-servicepoint;

    leaf device {
      type leafref {
        path "/ncs:devices/ncs:device/ncs:name";
      }
      mandatory true;
    }

    leaf description {
      type string;
      mandatory true;
    }

    list prefix-entry {
      key "sm-verb subnet-mask";

      leaf sm-verb {
        type enumeration {
          enum permit;
          enum deny;
        }
      }

      leaf subnet-mask {
        type string;
      }

      leaf op-verb {
        type enumeration {
          enum le;
          enum gt;
          enum eq;
        }
      }

      leaf op-length {
        type uint8 {
          range "0..32";
        }
      }
    }
  }
}
